-- Definition derived from openssl 3.0

OSCCA DEFINITIONS ::= BEGIN

    SM2Key ::= CHOICE {
        private     Private,
        public      Public
    }

    Signature ::= SEQUENCE {
        r       INTEGER,
        s       INTEGER
    }

    KeySet ::= SEQUENCE {
        number  INTEGER,
        prk     OCTET STRING,
        puk     [1] EXPLICIT BIT STRING
    }

    Private ::= SEQUENCE {
        number      INTEGER,
        ids         SEQUENCE OF OBJECT IDENTIFIER,
        keyset      OCTET STRING (CONTAINING KeySet)
    }

    Public ::= SEQUENCE {
        ids     SEQUENCE OF OBJECT IDENTIFIER,
        puk     BIT STRING

    }

END
